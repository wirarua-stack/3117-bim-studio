# SPDX-License-Identifier: GPL-3.0-or-later
# Restore or uninstall without deleting files. Keep the extracted package.
import importlib.util
from pathlib import Path
import FreeCADGui as Gui
from PySide import QtWidgets


def _manage_3117_installer():
    hint = globals().get("__file__")
    candidates = []
    if hint:
        location = Path(hint).resolve().parent
        candidates = [location, location.parent]
    root = next((path for path in candidates
                 if (path / "packaging" / "freecad_installer_ui.py").is_file()), None)
    if root is None:
        selected = QtWidgets.QFileDialog.getExistingDirectory(Gui.getMainWindow(),
            "เลือกโฟลเดอร์ชุดติดตั้ง 3117 ที่แตก ZIP และมีโฟลเดอร์ packaging")
        if not selected:
            return
        root = Path(selected)
    path = root / "packaging" / "freecad_installer_ui.py"
    if not path.is_file():
        QtWidgets.QMessageBox.critical(Gui.getMainWindow(), "3117 BIM Studio",
            "ไม่พบตัวช่วย กรุณาเลือกโฟลเดอร์ชุดติดตั้ง 3117 ที่แตก ZIP ทั้งชุดแล้ว")
        return
    spec = importlib.util.spec_from_file_location("bim3117_installer_ui", path)
    ui = importlib.util.module_from_spec(spec)
    spec.loader.exec_module(ui)
    ui.run(root, mode="manage")


_manage_3117_installer()
