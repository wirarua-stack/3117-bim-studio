# SPDX-License-Identifier: GPL-3.0-or-later
# Execute in FreeCAD after installing 3117 v0.4.0 and restarting FreeCAD.
import datetime
from pathlib import Path
import sys
import traceback

import FreeCAD as App
import FreeCADGui as Gui
from PySide import QtCore, QtGui
try:
    from PySide import QtWidgets
except ImportError:
    QtWidgets = QtGui

_bim3117_arch_root = None
try:
    _bim3117_arch_macro = Path(__file__).resolve()
    for _bim3117_arch_candidate in (_bim3117_arch_macro.parent, _bim3117_arch_macro.parent.parent):
        if (_bim3117_arch_candidate / "tests" / "freecad_architecture_gui.py").is_file():
            _bim3117_arch_root = _bim3117_arch_candidate
            break
except (NameError, TypeError, OSError):
    pass
if _bim3117_arch_root is None:
    _bim3117_arch_selected = QtWidgets.QFileDialog.getExistingDirectory(
        Gui.getMainWindow(), "Select the extracted 3117 v0.4.0 package folder")
    if _bim3117_arch_selected:
        _bim3117_arch_root = Path(_bim3117_arch_selected)
def _bim3117_arch_run_tests(_bim3117_arch_root=_bim3117_arch_root):
    try:
        if not (_bim3117_arch_root / "tests" / "freecad_architecture_gui.py").is_file():
            raise RuntimeError("The selected folder does not contain tests/freecad_architecture_gui.py")
        _bim3117_arch_output = (Path(App.getUserAppDataDir()) / "BIM3117_Test_Reports" /
                               ("Architecture_" + datetime.datetime.now().strftime("%Y%m%d_%H%M%S")))
        sys.path.insert(0, str(_bim3117_arch_root / "tests"))
        from freecad_architecture_gui import run
        _bim3117_arch_report = run(_bim3117_arch_output, keep_sample=True)
        _bim3117_arch_message = (
            "Passed {checks} Wall / Door GUI checks.\n\nReport, example and screenshot:\n{path}\n\n"
            "Next: close FreeCAD, reopen Architecture_Workbench.FCStd, change the shared wall type "
            "or L01, and check the walls and door openings with Undo / Redo."
        ).format(checks=_bim3117_arch_report["checks_passed"], path=str(_bim3117_arch_output))
        App.Console.PrintMessage(_bim3117_arch_message + "\n")
        QtWidgets.QMessageBox.information(Gui.getMainWindow(), "3117 Wall / Door test", _bim3117_arch_message)
    except BaseException as _bim3117_arch_error:
        App.Console.PrintError(traceback.format_exc() + "\n")
        QtWidgets.QMessageBox.warning(
            Gui.getMainWindow(), "3117 Wall / Door test failed", str(_bim3117_arch_error))


if _bim3117_arch_root is not None:
    # Native Undo/Redo actions stay disabled while a FreeCAD macro is running.
    # Return to the GUI event loop before the harness invokes those actions.
    QtCore.QTimer.singleShot(0, _bim3117_arch_run_tests)
